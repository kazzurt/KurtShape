"""Measure the real Qt shell in the recipe runner's hidden isolated process.

BENCH_HOLES and BENCH_REPEAT parameterize the historical GUI recipe. Native
controller metrics use the same plate geometry as the headless harness.
BENCH_PARAMETERS (run_gui_recipe -Parameters) is the parameter count for the
contract 3.2 parameter metrics; a build without parameter operations reports
that section unavailable instead of measuring something else.
"""
import http.client
import json
import os
from pathlib import Path
import sys
import threading
import time
import traceback

ROOT = Path(os.environ["KURTSHAPE_ROOT"]).resolve()
sys.dont_write_bytecode = True
sys.path.insert(0, str(ROOT / "tools" / "perf"))
sys.path.insert(0, str(ROOT / "tools"))
sys.path.insert(0, str(ROOT / "src"))
from bench_core import Benchmark, MEASUREMENT_POLICY, base_report, prepare_environment, resolve_output, run_sections, summary, timed
from kurtshape_evidence import evidence_dir

OUTPUT = None
REPORT = {"passed": False, "checks": [], "sections": {}, "timings": {}}
panel = None


def add_section(name, function):
    try:
        metrics = {key: summary(values) for key, values in function().items()}
        REPORT["timings"].update(metrics)
        REPORT["sections"][name] = {"status": "ok", "metrics": sorted(metrics)}
        REPORT["checks"].append(name + " measured inside the hidden GUI process")
    except Exception:
        REPORT["sections"][name] = {"status": "unavailable", "metrics": [], "error": traceback.format_exc()}


def validate():
    began = time.perf_counter()
    benchmark = None
    try:
        if HOLES < 1 or REPEAT < 1:
            raise RuntimeError("BENCH_HOLES and BENCH_REPEAT must be positive")
        benchmark = Benchmark(SCRATCH, "plate", HOLES, REPEAT, panel=panel)
        REPORT["fixture"] = benchmark.build()
        REPORT["engine"] = {"FreeCAD": App.Version(), "OCCT": benchmark.Part.OCC_VERSION}
        REPORT["growth"] = benchmark.growth
        REPORT["checks"].append("Real native plate volume and feature geometry verified")
        QtGui.QApplication.processEvents()
        REPORT["model"] = {"objects": len(benchmark.doc.Objects), "tree_items": len(panel.items)}

        def setup_parameters():
            """3b §14.4: N parameters (one formula in five) created natively in ONE setup recompute; with 0 the
            same no-op recompute runs, so both sides pay it (repeated managed recomputes grow inspect cost)."""
            doc = benchmark.doc
            if PARAMETERS > 0:
                from kurtshape import parameters as backend
                operations = set(panel.core.OPS)
                missing = sorted({"create_parameter", "edit_parameter", "list_parameters"} - operations)
                if missing:
                    raise RuntimeError("BENCH_PARAMETERS=" + str(PARAMETERS) + " needs parameter operations this build lacks: "
                                       + ", ".join(missing))
                vs = backend.create_set(doc)
                for index in range(PARAMETERS):
                    name = "p%02d" % index
                    vs.addProperty(backend.TYPES["length"], name, backend.GROUP)
                    setattr(vs, name, index + 1)
                    if index % 5 == 4:
                        vs.setExpression(name, "p%02d * 2" % (index - 1))
            doc.recompute()
            panel.core.observer.state(doc)["refresh"] = True
            panel.tick()
            QtGui.QApplication.processEvents()
            section = getattr(panel, "parameter_section", None)
            if PARAMETERS > 0:
                assert section is not None and len(section.order) == PARAMETERS, "The panel did not list every parameter"
                REPORT["checks"].append(str(PARAMETERS) + " parameters created natively in one recompute and listed")
        setup_parameters()

        def shell():
            retained = dict(panel.items)
            created = panel.feature_model.created
            section = getattr(panel, "parameter_section", None)
            section_created = section.created if hasattr(section, "created") else None
            refresh = timed(panel.refresh, REPEAT)[1]
            assert all(panel.items.get(key) is item for key, item in retained.items()), "Refresh replaced stable feature rows"
            assert panel.feature_model.created == created, "Unchanged refresh allocated feature rows"
            REPORT["checks"].append("Repeated real Panel refresh retains every stable history row")
            if hasattr(section, "created"):
                assert section.created == section_created, "Unchanged refresh allocated parameter rows"
                REPORT["checks"].append("Repeated real Panel refresh retains every parameter row")
            idle = timed(panel.tick, max(200, REPEAT))[1]

            def dirty_tick():
                panel.core.observer.state(benchmark.doc)["refresh"] = True
                panel.tick()
            dirty = timed(dirty_tick, REPEAT)[1]
            read = [read_request_tick() for _ in range(REPEAT)]
            REPORT["checks"].append("A queued bridge inspect is served by exactly the timed Panel.tick")
            return {"panel_refresh_ms": refresh, "tick_idle_ms": idle, "tick_after_refresh_flag_ms": dirty,
                    "tick_after_read_request_ms": read}

        def read_request_tick():
            """One Panel.tick that serves a read-only bridge inspect (and its refresh path).

            The request goes through the real loopback transport from a worker thread; the
            GUI thread waits (without processing events) until it is queued, so the timed
            tick is the one that dispatches it.
            """
            result = {}
            request = {"op": "inspect", "document_id": benchmark.state["document_id"], "measure": False}

            def send():
                connection = http.client.HTTPConnection("127.0.0.1", panel.bridge.server.server_port, timeout=60)
                try:
                    connection.request("POST", "/operation", body=json.dumps(request),
                                       headers={"Authorization": "Bearer " + panel.bridge.token,
                                                "Content-Type": "application/json"})
                    result["response"] = json.loads(connection.getresponse().read())
                except Exception:
                    result["error"] = traceback.format_exc()
                finally:
                    connection.close()
            assert panel.bridge.pending.empty(), "Bridge queue must be empty before the read-request tick"
            worker = threading.Thread(target=send, daemon=True)
            worker.start()
            deadline = time.monotonic() + 10
            while panel.bridge.pending.empty():
                if time.monotonic() > deadline or not worker.is_alive():
                    raise RuntimeError("Bridge inspect was not queued: " + str(result.get("error")))
                time.sleep(0.001)
            began = time.perf_counter()
            panel.tick()
            milliseconds = (time.perf_counter() - began) * 1000
            worker.join(30)
            assert panel.bridge.pending.empty(), "The timed tick did not serve the queued request"
            assert (result.get("response") or {}).get("ok") is True, result
            return milliseconds
        add_section("shell", shell)

        def parameters():
            """3b §14.4: section refresh with a forced key change, and one value commit (Enter until the refreshed
            field shows the new value) through the real panel."""
            from PySide6 import QtTest
            section = panel.parameter_section
            forced = timed(lambda: section.refresh(force=True), REPEAT)[1]
            commits = []
            for index in range(REPEAT):
                text = str(100 + index)
                field = section.rows["p00"].field
                field.setFocus(QtCore.Qt.MouseFocusReason)
                QtGui.QApplication.processEvents()
                field.selectAll()
                QtTest.QTest.keyClicks(field, text)
                began = time.perf_counter()
                QtTest.QTest.keyClick(field, QtCore.Qt.Key_Return)
                deadline = time.monotonic() + 30
                while section.rows["p00"].field.edited or section.rows["p00"].field.text() != text:
                    if time.monotonic() > deadline:
                        raise RuntimeError("The parameter commit did not complete: " + section.error.text())
                    QtGui.QApplication.processEvents()
                commits.append((time.perf_counter() - began) * 1000)
            REPORT["checks"].append("Parameter value commits applied through the real panel")
            return {"parameter_section_refresh_ms": forced, "parameter_commit_ms": commits}
        if PARAMETERS > 0:
            add_section("parameters", parameters)

        def checkpoints():
            snapshots = []
            panel.core.recovery.close()
            panel.core.recovery.last.clear()
            panel.responsiveness.last_activity = time.perf_counter()
            panel.checkpoint_projects()
            assert not panel.core.recovery.pending, "Active input scheduled a native checkpoint"
            REPORT["checks"].append("Recent input defers the native recovery snapshot")
            for _ in range(REPEAT):
                panel.core.recovery.last.clear()
                panel.responsiveness.last_activity = time.perf_counter() - 3
                began = time.perf_counter()
                panel.checkpoint_projects()
                snapshots.append((time.perf_counter() - began) * 1000)
                identifier = panel.core.identifier(benchmark.doc)
                revision = panel.core._meta(benchmark.doc).Revision
                assert identifier in panel.core.recovery.pending, "Idle GUI checkpoint did not schedule publication"
                # Test-only durability wait; interactive capture returns above.
                _, record = panel.core.recovery.read(panel.core.recovery.directory / (identifier + ".json"))
                assert record["revision"] == revision, "GUI checkpoint manifest has the wrong revision"
                assert panel.core.recovery.last.get(identifier, (None, None))[1] == revision
            idle = timed(panel.checkpoint_projects, max(20, REPEAT))[1]
            return {"checkpoint_projects_native_snapshot_ms": snapshots, "checkpoint_projects_idle_ms": idle}
        add_section("gui_checkpoint", checkpoints)

        def filters():
            from kurtshape import navigation
            app = QtGui.QApplication.instance()
            installed = [panel, panel.workspace_preferences, panel.router._filter, panel.responsiveness,
                         navigation._double_middle_filter, getattr(app, "_kurtshape_theme_filter", None)]
            installed = [item for item in installed if item is not None]
            count = 3000

            def moves():
                for index in range(count):
                    point = QtCore.QPointF(5 + index % 7, 5)
                    event = QtGui.QMouseEvent(QtCore.QEvent.MouseMove, point, point,
                                             QtCore.Qt.NoButton, QtCore.Qt.NoButton, QtCore.Qt.NoModifier)
                    app.sendEvent(panel.message, event)
            with_filters = timed(moves, REPEAT)[1]
            removed = []
            try:
                for item in installed:
                    app.removeEventFilter(item)
                    removed.append(item)
                without_filters = timed(moves, REPEAT)[1]
            finally:
                for item in removed:
                    app.installEventFilter(item)
            REPORT["app_event_filters"] = {"count": len(installed),
                                            "classes": [type(item).__name__ for item in installed],
                                            "events_per_sample": count,
                                            "us_per_event_with": summary(with_filters)["median"] * 1000 / count,
                                            "us_per_event_without": summary(without_filters)["median"] * 1000 / count}
            return {"app_event_filters_with_ms": with_filters,
                    "app_event_filters_without_ms": without_filters}
        add_section("event_filters", filters)
        run_sections(benchmark, REPORT, ["edits", "inspect", "checkpoint", "preview"])
        REPORT["passed"] = all(section["status"] == "ok" for section in REPORT["sections"].values())
        panel.isometric()
        panel.fit()
        QtGui.QApplication.processEvents()
        screenshot = evidence_dir("perf") / "bench-gui-working" / "plate-viewport.png"
        screenshot.parent.mkdir(parents=True, exist_ok=True)
        if not panel.main.grab().save(str(screenshot)):
            raise RuntimeError("Could not save the benchmark viewport screenshot")
        REPORT["screenshot"] = str(screenshot)
        REPORT["controller_timings"] = panel.core.timings.report()
    except Exception:
        REPORT.update(passed=False, error=traceback.format_exc())
    finally:
        REPORT["seconds"] = time.perf_counter() - began
        cleanup_errors = []
        if panel:
            for cleanup in (panel.shutdown,):
                try:
                    cleanup()
                except Exception:
                    cleanup_errors.append(traceback.format_exc())
        try:
            document_names = list(App.listDocuments())
        except Exception:
            cleanup_errors.append(traceback.format_exc())
            document_names = []
        for name in document_names:
            try:
                App.closeDocument(name)
            except Exception:
                cleanup_errors.append(traceback.format_exc())
        if cleanup_errors:
            REPORT.update(passed=False, cleanup_errors=cleanup_errors)
        try:
            OUTPUT.parent.mkdir(parents=True, exist_ok=True)
            OUTPUT.write_text(json.dumps(REPORT, indent=2, allow_nan=False) + "\n", encoding="utf-8")
            print(json.dumps({"passed": REPORT["passed"], "report": str(OUTPUT), "sections": REPORT["sections"]}), flush=True)
        finally:
            QtCore.QTimer.singleShot(250, QtGui.QApplication.instance().quit)


try:
    OUTPUT = resolve_output(os.environ.get("BENCH_GUI_OUT"), "bench-gui.json")
    HOLES = int(os.environ.get("BENCH_HOLES", "20"))
    REPEAT = int(os.environ.get("BENCH_REPEAT", "3"))
    PARAMETERS = int(os.environ.get("BENCH_PARAMETERS", "0") or "0")
    REPORT = base_report("plate", HOLES, "Hidden FreeCAD GUI; Qt events synthesized inside this process; native fixture through Panel.operation")
    REPORT.update(gui_process_pid=os.getpid(), repeat=REPEAT, parameters=PARAMETERS, measurement_level=False,
                  measurement_policy=MEASUREMENT_POLICY)
    session = Path(os.environ["KURTSHAPE_SESSION_DIR"]).resolve()
    SCRATCH = prepare_environment(session / "benchmark-working")
    import FreeCAD as App
    import FreeCADGui as Gui
    from PySide import QtCore, QtGui
    main = Gui.getMainWindow()
    main.hide()
    main.setAttribute(QtCore.Qt.WA_DontShowOnScreen, True)
    main.resize(1200, 800)
    main.show()
    began = time.perf_counter()
    from kurtshape.ui import start
    panel = start()
    QtGui.QApplication.processEvents()
    REPORT["timings"]["startup_ms"] = summary([(time.perf_counter() - began) * 1000])
    REPORT["sections"]["startup"] = {"status": "ok", "metrics": ["startup_ms"]}
    REPORT["checks"].append("Qt shell started using the isolated profile")
    QtCore.QTimer.singleShot(1800, validate)
except Exception:
    REPORT.update(passed=False, error=traceback.format_exc())
    try:
        if OUTPUT is not None:
            OUTPUT.parent.mkdir(parents=True, exist_ok=True)
            OUTPUT.write_text(json.dumps(REPORT, indent=2) + "\n", encoding="utf-8")
        print(REPORT["error"], flush=True)
    finally:
        from PySide import QtCore, QtGui
        QtCore.QTimer.singleShot(250, QtGui.QApplication.instance().quit)
