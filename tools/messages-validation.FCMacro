"""Production Messages checks in a hidden native process with its own profile.

Launch with tools/validate-messages.ps1. Original documents and the user's
running FreeCAD process are never accessed. The bridge is replaced with a
queue stub; production Panel, report capture, Qt button events and core rejection
paths are exercised. Native C++ networking is not intercepted by this helper.
"""
import json
import os
from pathlib import Path
import queue
import socket
import sys
import time
import traceback

root = Path(os.environ['KURTSHAPE_ROOT']).resolve()
sys.path.insert(0, str(root / "tools"))
sys.dont_write_bytecode = True
from kurtshape_evidence import evidence_dir
session = Path(os.environ['KURTSHAPE_SESSION_DIR']).resolve()
assert session.is_relative_to(root / 'runtime'), 'Use a private validation profile'
assert Path(os.environ['FREECAD_USER_HOME']).resolve().is_relative_to(session)
sys.path.insert(0, str(root / 'src'))


def deny_network(*args, **kwargs):
    raise RuntimeError('Python networking disabled for Messages validation')


socket.socket.connect = deny_network
socket.socket.connect_ex = deny_network
socket.socket.sendto = deny_network
socket.create_connection = deny_network
socket.getaddrinfo = deny_network
import FreeCAD as App
import FreeCADGui as Gui
from PySide import QtCore, QtGui
from PySide6 import QtTest, QtWidgets
from kurtshape import ui


class NoSocketTransport:
    def __init__(self, *args):
        self.pending = queue.Queue()
    def tick(self):
        return False
    def close(self):
        pass


class HiddenPopupFilter(QtCore.QObject):
    def eventFilter(self, watched, event):
        if event.type() in {QtCore.QEvent.Polish, QtCore.QEvent.Show} and isinstance(watched, QtWidgets.QWidget) and watched.isWindow():
            watched.setAttribute(QtCore.Qt.WA_DontShowOnScreen, True)
        return False


ui.Bridge = NoSocketTransport
application = QtWidgets.QApplication.instance()
main = Gui.getMainWindow()
main.hide()
main.setAttribute(QtCore.Qt.WA_DontShowOnScreen, True)
main.resize(1440, 920)
main.show()
hidden_popups = HiddenPopupFilter(application)
application.installEventFilter(hidden_popups)
clipboard = application.clipboard()
original_clipboard = QtCore.QMimeData()
original_mime = clipboard.mimeData()
if original_mime is not None:
    for mime_format in original_mime.formats():
        original_clipboard.setData(mime_format, QtCore.QByteArray(original_mime.data(mime_format)))
output = evidence_dir("messages-behavior")
output.mkdir(parents=True, exist_ok=True)
result = {
    'passed': False,
    'checks': [],
    'method': 'Production Panel, native Console/ReportOutput, actual Qt Messages/copy/close-button events and text clipboard shortcuts in an independent hidden native process; original clipboard MIME data restored',
    'runtime_profile': str(session.relative_to(root)),
    'engine': App.Version(),
    'limits': 'Small synthetic project; native warnings/errors are deliberately generated in this isolated profile. Native C++ networking is not intercepted.',
}
panel = None
finished = False
started = time.perf_counter()


def check(label, condition):
    assert condition, label
    result['checks'].append(label)


def wait(ms=100):
    QtTest.QTest.qWait(ms)


def click(widget):
    QtTest.QTest.mouseClick(widget, QtCore.Qt.LeftButton)
    wait()


def message_menu_action(label, action_text):
    observed = {}
    def choose():
        menu = application.activePopupWidget()
        if not isinstance(menu, QtGui.QMenu):
            menu = next((child for child in label.findChildren(QtGui.QMenu) if child.isVisible()), None)
        if menu is None:
            observed['error'] = 'Status context menu did not open'
            # Close any label-owned menu even when the hidden-window platform
            # does not report it as an active popup, keeping exec_ bounded.
            for child in label.findChildren(QtGui.QMenu):
                child.close()
            return
        observed['actions'] = {action.text(): action.isEnabled() for action in menu.actions() if not action.isSeparator()}
        action = next((action for action in menu.actions() if action.text() == action_text), None)
        if action is not None and action.isEnabled():
            action.trigger()
            observed['triggered'] = action_text
        menu.close()
    QtCore.QTimer.singleShot(20, choose)
    panel.show_message_menu(label.rect().center(), label)
    return observed


def finish():
    global finished
    if finished:
        return
    finished = True
    result['elapsed_seconds'] = round(time.perf_counter() - started, 3)
    try:
        if panel is not None:
            result['messages_text'] = panel.messages.toPlainText()
            result['status_text'] = panel.message.text()
            result['button_text'] = panel.messages_button.text()
            result['unread'] = panel.unread_messages
            main.grab().save(str(output / 'messages-window.png'))
            panel.shutdown()
        for name in list(App.listDocuments()):
            gui_doc = Gui.getDocument(name)
            if gui_doc and gui_doc.getInEdit():
                gui_doc.resetEdit()
            doc = App.getDocument(name)
            if doc.HasPendingTransaction:
                doc.abortTransaction()
            doc.setClosable(True)
            App.closeDocument(name)
        result['cleanup_complete'] = True
    except Exception:
        result['passed'] = False
        result['cleanup_error'] = traceback.format_exc()
    finally:
        clipboard.setMimeData(original_clipboard)
        result['clipboard_restored'] = True
        (output / 'gui-result.json').write_text(json.dumps(result, indent=2), encoding='utf-8')
        application.removeEventFilter(hidden_popups)
        QtCore.QTimer.singleShot(0, application.quit)


def validate():
    global panel
    try:
        prefs = App.ParamGet('User parameter:BaseApp/Preferences/OutputWindow')
        prefs.SetBool('checkMessage', True)
        startup_marker = 'messages pre-panel startup: retained once ☀ 😀'
        App.Console.PrintMessage(startup_marker + '\n')
        wait()
        panel = ui.start()
        wait(500)
        report_widget = next(w for w in main.findChildren(QtGui.QTextEdit) if w.metaObject().className() == 'Gui::DockWnd::ReportOutput')
        report_dock = next(w for w in main.findChildren(QtGui.QDockWidget) if w.objectName() == 'Report view')
        check('Messages starts hidden with a manually accessible button', panel.messages_dock.isHidden() and panel.messages_button.isVisible() and not panel.messages_button.isChecked())
        check('Native startup output emitted before Panel attaches is retained exactly once', panel.messages.toPlainText().count(startup_marker) == 1)
        startup_output = report_widget.toPlainText() + (session / 'freecad.log').read_text(encoding='utf-8', errors='replace')
        check('App startup no longer produces the QStatusBar insertPermanentWidget warning', 'QStatusBar::insertPermanentWidget' not in startup_output)
        # Slice A/B U7 (A-08): the startup backlog is retained but never lights the Messages dot.
        result['startup_button'] = {'text': panel.messages_button.text(), 'alerts': panel.unread.alerts, 'unread': panel.unread_messages}
        check('The startup backlog does not light the Messages dot or count as unread',
              panel.messages_button.text() == 'Messages' and panel.unread.alerts == 0 and panel.unread_messages == 0)
        for key in ('checkWarning', 'checkError', 'checkMessage', 'checkLogging'):
            prefs.SetBool(key, True)
        # Exercise the independent native preference that used to reopen its own
        # report dock, even though the KurtShape Messages panel was hidden.
        for key in ('checkShowReportViewOnError', 'checkShowReportViewOnWarning', 'checkShowReportViewOnNormalMessage', 'checkShowReportViewOnLogMessage'):
            prefs.SetBool(key, True)
        panel.notify('Messages test: modeling status remains visible')
        status = panel.message.text()
        status_style = panel.message.styleSheet()
        sent = [
            (App.Console.PrintMessage, 'messages normal: information only\n'),
            (App.Console.PrintWarning, 'messages warning: diagnostic only\n'),
            (App.Console.PrintError, 'messages native error: details retained\n'),
            (App.Console.PrintLog, 'messages log: troubleshooting details\n'),
        ]
        dots = {}
        alerts_before = panel.unread.alerts
        for printer, text in sent:
            before_unread = panel.unread_messages
            before_alerts = panel.unread.alerts
            printer(text)
            wait()
            dots[text.split(':', 1)[0]] = ('•' in panel.messages_button.text(), panel.unread.alerts - before_alerts)
            check('Native ' + text.split(':', 1)[0] + ' is retained once without opening a dock or interrupting status',
                  panel.messages.toPlainText().count(text.strip()) == 1 and panel.messages_dock.isHidden() and report_dock.isHidden()
                  and panel.message.text() == status and panel.message.styleSheet() == status_style and panel.unread_messages > before_unread)
        check('Unread log entries have a quiet indicator and full count in hover help', panel.unread_messages > 0 and '•' in panel.messages_button.text() and 'unread' in panel.messages_button.toolTip())
        result['native_dots'] = dots
        result['alerts_before_native_lines'] = alerts_before
        check('An informational native line does not light the Messages dot; a warning and an error do (A-08)',
              dots['messages normal'] == (alerts_before > 0, 0) and dots['messages warning'] == (True, 1)
              and dots['messages native error'] == (True, 1) and dots['messages log'] == (True, 0))
        rejected = panel.operation('set_parameter', feature='NoSuchFeature', parameter='Length', value='1 mm')
        wait()
        error_text = panel.message.text()
        check('A rejected controller operation shows red readable status and retains its error without opening Messages',
              rejected is None and ui.COLORS['error'] in panel.message.styleSheet() and error_text in panel.messages.toPlainText()
              and panel.messages_dock.isHidden() and not panel.messages_button.isChecked())
        error = panel.last_operation_error or {}
        result['rejected_status'] = error_text
        check('The rejected operation status names its feature and code; Messages keeps its other fields as JSON and the message once (C-03)',
              error.get('code') and error_text.endswith(' · ' + error['code']) and 'NoSuchFeature' in error_text
              and ('  details: ' + json.dumps({k: v for k, v in error.items() if k != 'message'}, sort_keys=True, default=str,
                                              ensure_ascii=False)) in panel.messages.toPlainText()
              and panel.messages.toPlainText().count(error.get('message', '?')) == 1)
        # Slice A/B U7 gate (C-03): a Part Studio Remove that removes nothing, sent through the panel's own
        # operation path, names the failing feature and code in the status line and selects the feature
        # the request named in the history and the viewport (the rolled-back Remove has no row; its
        # profile does).
        for op, args in (('new', {}), ('sketch_rectangle', {'id': 'Plate', 'width': 20, 'height': 12}),
                         ('pad', {'id': 'Block', 'profile': 'Plate', 'length': 6, 'operation': 'new'}),
                         ('sketch_circle', {'id': 'Air', 'x': 10, 'y': 6, 'diameter': 4, 'plane': 'XY'})):
            assert panel.operation(op, **args), op + ': ' + panel.message.text()
        check('The gate document is a Part Studio', panel.state['studio']['enabled'])
        # The GUI's operation path (as Confirm uses it): a blind Remove from the sketch, first one way,
        # then the other, until one removes nothing (a direction that cuts the plate is undone).
        Gui.Selection.clearSelection()
        panel.features.clearSelection()
        unread_before = panel.unread.alerts
        attempts = []
        for reversed_ in (True, False):
            rows = len(panel.state['features'])
            outcome = panel.operation('pad', id='ExtrudeRemove', profile='Air', length=5, operation='remove', reversed=reversed_)
            attempts.append({'reversed': reversed_, 'committed': outcome is not None})
            if outcome is None:
                break
            assert panel.operation('undo') and len(panel.state['features']) == rows, 'undo of the cutting Remove'
            unread_before = panel.unread.alerts
        wait()
        error = panel.last_operation_error or {}
        status_line = panel.message.text()
        selected = panel.history_controller.selected_ids()
        native = [entry.ObjectName for entry in Gui.Selection.getSelectionEx()]
        # The error's own feature, else its trigger's, else the request's new feature (ExtrudeRemove).
        named = error.get('feature') or (error.get('trigger') or {}).get('feature') or 'ExtrudeRemove'
        result['remove_nothing'] = {'attempts': attempts, 'error': error, 'status': status_line, 'selected': selected,
                                    'native_selection': native}
        check('The rejected Remove names the failing feature and the code in the red status line',
              error.get('code') and named and status_line.endswith(' · ' + named + ' · ' + error['code'])
              and status_line.startswith(error.get('message', '?')) and ui.COLORS['error'] in panel.message.styleSheet())
        check('The rejected Remove selects the feature it names in the history and the viewport (the profile it was made from)',
              selected == ['Air'] and native == ['Air'])
        check('Messages keeps the rejection and the dot counts it', status_line in panel.messages.toPlainText()
              and '"code": "' + error['code'] + '"' in panel.messages.toPlainText() and panel.unread.alerts > unread_before)
        # Slice A/B U7: with a model object selected (the failing feature above), Ctrl+A / Ctrl+C in the
        # read-only Messages view copy its text; FreeCAD's Std_Copy (an Object Selection dialog) must not
        # open. A guard timer closes and records any modal dialog so a regression fails instead of hanging.
        selection_present = [entry.ObjectName for entry in Gui.Selection.getSelectionEx()]
        modal_seen = []
        def close_modal():
            modal = application.activeModalWidget()
            if modal is not None:
                modal_seen.append(modal.metaObject().className() + ': ' + modal.windowTitle())
                modal.close()
        guard = QtCore.QTimer()
        guard.setInterval(200)
        guard.timeout.connect(close_modal)
        panel.messages_dock.show()
        wait()
        guard.start()
        try:
            panel.messages.setFocus(QtCore.Qt.OtherFocusReason)
            wait()
            QtTest.QTest.keyClick(panel.messages, QtCore.Qt.Key_A, QtCore.Qt.ControlModifier)
            QtTest.QTest.keyClick(panel.messages, QtCore.Qt.Key_C, QtCore.Qt.ControlModifier)
            wait(400)
        finally:
            guard.stop()
        result['copy_with_model_selection'] = {'selection': selection_present, 'modal_seen': modal_seen,
                                               'clipboard_matches': clipboard.text() == panel.messages.toPlainText()}
        check('Ctrl+C in Messages with a model object selected copies the text and opens no native dialog',
              selection_present == ['Air'] and not modal_seen and clipboard.text() == panel.messages.toPlainText())
        panel.messages_dock.hide()
        wait()
        # The clipboard checks below run, as before this gate, with no model selection.
        Gui.Selection.clearSelection()
        panel.features.clearSelection()
        wait()
        click(panel.messages_button)
        check('Actual Messages button opens details and clears unread count', panel.messages_dock.isVisible() and panel.messages_button.isChecked() and panel.unread_messages == 0 and panel.messages_button.text() == 'Messages')
        App.Console.PrintMessage('messages while open: read immediately\n')
        wait()
        check('New output while Messages is open does not create unread count', panel.unread_messages == 0 and 'messages while open: read immediately' in panel.messages.toPlainText())
        close_button = panel.messages_dock.findChild(QtWidgets.QAbstractButton, 'qt_dockwidget_closebutton')
        check('Messages exposes its normal dock close button', close_button is not None)
        click(close_button)
        check('Closing Messages synchronizes the access button', panel.messages_dock.isHidden() and not panel.messages_button.isChecked())
        panel.notify('messages managed error after close', 'error')
        check('Later explicit errors respect the closed Messages panel and create unread count', panel.messages_dock.isHidden() and panel.unread_messages > 0 and panel.messages.toPlainText().count('messages managed error after close') == 1)
        # Native Clear and bounded ReportOutput trimming must not remove mirrored
        # evidence or re-append old retained lines as if they were new messages.
        retained = 'messages normal: information only'
        report_widget.clear()
        wait()
        check('Clearing the native report preserves KurtShape diagnostic history', panel.messages.toPlainText().count(retained) == 1)
        report_widget.document().setMaximumBlockCount(2)
        for printer, text in [
            (App.Console.PrintMessage, 'messages trim one: ☀ 😀 unicode\n'),
            (App.Console.PrintWarning, 'messages trim two: retained once\n'),
            (App.Console.PrintError, 'messages trim three: retained once\n'),
        ]:
            printer(text)
            wait()
            check('Native ' + text.split(':', 1)[0] + ' survives UTF-16 cursor extraction/front trimming once', panel.messages.toPlainText().count(text.strip()) == 1)
        check('Native front trimming does not duplicate previously mirrored entries', panel.messages.toPlainText().count('messages trim one: ☀ 😀 unicode') == 1 and panel.messages.toPlainText().count('messages trim two: retained once') == 1)
        App.Console.PrintMessage('messages fragmented: first half ')
        wait()
        App.Console.PrintMessage('second half 😀\n')
        wait()
        result['fragment_continuity_preserved'] = 'messages fragmented: first half second half 😀' in panel.messages.toPlainText()
        check('Partial native messages preserve both their text and Unicode without opening a dock', 'messages fragmented: first half' in panel.messages.toPlainText() and 'second half 😀' in panel.messages.toPlainText() and panel.messages_dock.isHidden() and report_dock.isHidden())
        check('Native warnings and errors do not overwrite the explicit application error status', panel.message.text() == 'messages managed error after close' and ui.COLORS['error'] in panel.message.styleSheet())
        click(panel.messages_button)
        check('Messages can be reopened after native Clear/trim with full retained details and unread reset', panel.messages_dock.isVisible() and panel.unread_messages == 0 and panel.messages.toPlainText().count(retained) == 1)
        check('Messages exposes an explicit Copy all button', panel.copy_messages_button.isVisible() and panel.copy_messages_button.objectName() == 'KurtShapeCopyMessagesButton')
        cursor = panel.messages.textCursor()
        cursor.setPosition(0)
        cursor.setPosition(min(24, panel.messages.document().characterCount() - 1), QtGui.QTextCursor.KeepAnchor)
        panel.messages.setTextCursor(cursor)
        selection_before = (cursor.anchor(), cursor.position(), cursor.selectedText())
        status_before = (panel.message.text(), panel.message.styleSheet())
        unread_before = panel.unread_messages
        expected_copy = panel.messages.toPlainText()
        click(panel.copy_messages_button)
        check('Actual Copy all button copies exact retained Unicode and newlines', clipboard.text() == expected_copy and '\n' in expected_copy and '☀ 😀' in expected_copy)
        cursor = panel.messages.textCursor()
        check('Copy all preserves error status, unread count, selection and retained history',
              (panel.message.text(), panel.message.styleSheet()) == status_before and panel.unread_messages == unread_before
              and (cursor.anchor(), cursor.position(), cursor.selectedText()) == selection_before and panel.messages.toPlainText() == expected_copy)
        model_clipboard_actions = []
        original_copy_action = panel.router.callbacks['general.copy']
        original_paste_action = panel.router.callbacks['general.paste']
        panel.router.callbacks['general.copy'] = lambda: model_clipboard_actions.append('copy')
        panel.router.callbacks['general.paste'] = lambda: model_clipboard_actions.append('paste')
        clipboard_target = None
        try:
            panel.messages.setFocus(QtCore.Qt.OtherFocusReason)
            wait()
            QtTest.QTest.keyClick(panel.messages, QtCore.Qt.Key_A, QtCore.Qt.ControlModifier)
            QtTest.QTest.keyClick(panel.messages, QtCore.Qt.Key_C, QtCore.Qt.ControlModifier)
            wait()
            check('Ctrl+A then Ctrl+C copies read-only Messages without invoking model copy',
                  clipboard.text() == expected_copy and panel.messages.isReadOnly() and not model_clipboard_actions)
            clipboard_target = QtGui.QPlainTextEdit(main)
            clipboard_target.resize(240, 80)
            clipboard_target.show()
            clipboard_target.setFocus(QtCore.Qt.OtherFocusReason)
            wait()
            QtTest.QTest.keyClick(clipboard_target, QtCore.Qt.Key_V, QtCore.Qt.ControlModifier)
            wait()
            check('Copied Messages paste exactly into a text target without invoking model paste',
                  clipboard_target.toPlainText() == expected_copy and not model_clipboard_actions)
            clipboard_target.hide()
            status_copy_text = 'messages status copy: <native> ☀ 😀'
            panel.notify(status_copy_text, 'error')
            panel.message.setFocus(QtCore.Qt.OtherFocusReason)
            panel.message.setSelection(0, len(status_copy_text.encode('utf-16-le')) // 2)
            wait()
            check('Status errors are plain text and selectable with keyboard focus',
                  panel.message.textFormat() == QtCore.Qt.PlainText
                  and panel.message.textInteractionFlags() & QtCore.Qt.TextSelectableByMouse
                  and panel.message.textInteractionFlags() & QtCore.Qt.TextSelectableByKeyboard
                  and panel.message.focusPolicy() == QtCore.Qt.StrongFocus and panel.message.selectedText() == status_copy_text)
            QtTest.QTest.keyClick(panel.message, QtCore.Qt.Key_C, QtCore.Qt.ControlModifier)
            wait()
            check('Ctrl+C on a selected status error copies exact text without invoking model copy or changing status',
                  clipboard.text() == status_copy_text and panel.message.text() == status_copy_text
                  and ui.COLORS['error'] in panel.message.styleSheet() and not model_clipboard_actions)
            long_status_text = 'messages long status copy: <native> ☀ 😀 ' + ('diagnostic detail ' * 45)
            original_maximum_width = panel.message.maximumWidth()
            try:
                panel.message.setMaximumWidth(220)
                panel.notify(long_status_text, 'error')
                wait()
                check('Long diagnostic status is visibly clipped for the full-message copy test',
                      panel.message.fontMetrics().boundingRect(long_status_text).width() > panel.message.width())
                selection_text = 'diagnostic detail'
                selection_start = len(long_status_text[:long_status_text.index(selection_text)].encode('utf-16-le')) // 2
                panel.message.setSelection(selection_start, len(selection_text))
                menu_result = message_menu_action(panel.message, 'Copy selection')
                check('Status context-menu Copy selection copies only the selected diagnostic text',
                      menu_result.get('triggered') == 'Copy selection' and clipboard.text() == selection_text
                      and panel.message.text() == long_status_text and not model_clipboard_actions)
                panel.message.setSelection(0, 0)
                menu_result = message_menu_action(panel.message, 'Copy message')
                result['copy_message_probe'] = {'menu': menu_result, 'clipboard_matches': clipboard.text() == long_status_text,
                                                'status_matches': panel.message.text() == long_status_text, 'status': panel.message.text()[:200],
                                                'model_clipboard_actions': list(model_clipboard_actions)}
                check('Status context-menu Copy message copies the full clipped Unicode diagnostic',
                      menu_result.get('triggered') == 'Copy message' and clipboard.text() == long_status_text
                      and menu_result.get('actions', {}).get('Copy selection') is False
                      and panel.message.text() == long_status_text and ui.COLORS['error'] in panel.message.styleSheet() and not model_clipboard_actions)
            finally:
                panel.message.setMaximumWidth(original_maximum_width)
            panel.notify(status_copy_text, 'error')
        finally:
            panel.router.callbacks['general.copy'] = original_copy_action
            panel.router.callbacks['general.paste'] = original_paste_action
            if clipboard_target is not None:
                clipboard_target.hide()
                clipboard_target.deleteLater()
            result['model_clipboard_actions'] = model_clipboard_actions
        main.grab().save(str(output / 'messages-copy-controls.png'))
        click(panel.messages_button)
        check('Clicking Messages a second time closes it', panel.messages_dock.isHidden() and not panel.messages_button.isChecked())
        App.Console.PrintWarning('messages hidden copy: unread details retained\n')
        wait()
        hidden_status_before = (panel.message.text(), panel.message.styleSheet())
        hidden_unread_before = panel.unread_messages
        hidden_copy = panel.messages.toPlainText()
        panel.copy_messages()
        check('Copying hidden Messages preserves unread count, dock visibility and the current error status',
              clipboard.text() == hidden_copy and hidden_unread_before > 0 and panel.unread_messages == hidden_unread_before
              and panel.messages_dock.isHidden() and not panel.messages_button.isChecked()
              and (panel.message.text(), panel.message.styleSheet()) == hidden_status_before)
        result['passed'] = True
    except Exception:
        result['error'] = traceback.format_exc()
    finally:
        finish()


def timeout():
    if not finished:
        result['error'] = 'Messages validation exceeded its 60-second bound'
        finish()


QtCore.QTimer.singleShot(100, validate)
QtCore.QTimer.singleShot(60000, timeout)
