"""Hidden GUI checks: tool search, toolbar, one Extrude tool, direction, sketch fill."""
import json
import os
from pathlib import Path
import sys
import traceback

root = Path(os.environ["KURTSHAPE_ROOT"])
sys.path.insert(0, str(root / "tools"))
sys.dont_write_bytecode = True
from kurtshape_evidence import evidence_dir
sys.path.insert(0, str(root / "src"))
import FreeCAD as App
import FreeCADGui as Gui
import Part
from PySide import QtCore, QtGui
from PySide6 import QtTest, QtWidgets
from shiboken6 import isValid
main = Gui.getMainWindow()
main.hide()
main.setAttribute(QtCore.Qt.WA_DontShowOnScreen, True)
main.resize(1440, 920)
main.show()
from kurtshape.ui import start
from kurtshape.core import intent_signature
from preview_validation import wait_for_exact
panel = start()
output = evidence_dir("everyday-ui")
output.mkdir(parents=True, exist_ok=True)
report = {"passed": False, "checks": [], "samples": {}, "method": "Separate hidden native GUI; real search dialog, toolbar, buttons and rendered pixels"}


def check(label, condition):
    assert condition, label + ": " + panel.message.text() + " | " + panel.editor.verdict.text()
    report["checks"].append(label)


def call(op, **args):
    state = panel.operation(op, **args)
    assert state, panel.message.text()
    return state


def wait(ms=80):
    QtTest.QTest.qWait(ms)


def doc():
    return App.activeDocument()


def viewport():
    area = next(area for area in main.findChildren(QtWidgets.QMdiArea) if area.activeSubWindow())
    return next(widget for widget in area.activeSubWindow().findChildren(QtWidgets.QWidget)
                if widget.metaObject().className() == "QOpenGLWidget")


def search(text):
    dialog = panel.show_tool_search()
    field = dialog.findChild(QtWidgets.QLineEdit, "KurtShapeToolSearchQuery")
    table = dialog.findChild(QtWidgets.QTreeWidget, "KurtShapeToolSearchResults")
    field.clear()
    QtTest.QTest.keyClicks(field, text)
    wait(40)
    rows = [[table.topLevelItem(i).text(c) for c in range(4)] for i in range(table.topLevelItemCount())]
    return dialog, field, rows


def pixel(point3d):
    view = Gui.activeDocument().activeView()
    view.redraw()
    wait(300)
    frame = viewport().grab().toImage()
    x, y = view.getPointOnViewport(point3d)
    x, y = round(x), frame.height() - 1 - round(y)
    colors = [frame.pixelColor(i, j).getRgb()[:3] for i in range(x - 1, x + 2) for j in range(y - 1, y + 2)]
    return tuple(sorted(colors)[len(colors) // 2])


def button(bar, text):
    action = next(action for action in bar.actions() if action.text() == text)
    return bar.widgetForAction(action)


def footer_agrees():
    panel.restore_status()
    return panel.message.text() == panel.status.text()


def validate():
    try:
        # Slice A/B U7 (A-10): an empty part says so, and the footer repeats the status line.
        report["samples"]["startup_status"] = panel.status.text()
        check("A new empty part reads 'Empty part · mm', not 'Sketches only'", panel.status.text() == "Empty part · mm")
        check("The footer agrees with the document status", footer_agrees())
        # Slice A/B U7 (A-05): hover labels show every key, single keys included, from the registry.
        labels = {name: panel.toolbar_labels.text_for(button(bar, name)) for bar, name in
                  ((panel.model_bar, "Sketch"), (panel.model_bar, "Extrude"), (panel.model_bar, "Fit"),
                   (panel.model_bar, "Normal"), (panel.model_bar, "Show planes"), (panel.sketch_bar, "Line"),
                   (panel.sketch_bar, "Rectangle"), (panel.sketch_bar, "Dimension"), (panel.sketch_bar, "Spline"),
                   (panel.document_bar, "Save"), (panel.assembly_bar, "Joints"))}
        report["samples"]["hover_labels"] = labels
        check("Hover labels show single-key shortcuts", labels["Fit"] == "Fit  (F)" and labels["Normal"] == "Normal  (N)"
              and labels["Show planes"] == "Show planes  (P)" and labels["Line"] == "Line  (L)"
              and labels["Rectangle"] == "Rectangle  (G)" and labels["Dimension"] == "Dimension  (D)"
              and labels["Joints"] == "Joints  (J)")
        check("Hover labels keep modifier shortcuts and omit absent ones",
              labels["Sketch"] == "Sketch  (Shift+S)" and labels["Extrude"] == "Extrude  (Shift+E)"
              and labels["Save"] == "Save  (Ctrl+S)" and labels["Spline"] == "Spline")
        check("The editor's Confirm and Cancel labels show Enter and Escape",
              panel.toolbar_labels.text_for(panel.confirm) in {"Confirm  (Enter)", "Finish sketch"}
              and panel.toolbar_labels.text_for(panel.cancel) == "Cancel  (Escape)")
        from kurtshape.shortcuts import load_registry
        rebinding = output / "shortcuts.user.json"
        rebinding.write_text(json.dumps({"schema_version": 1, "bindings": {"sketch.line": "Shift+Alt+L", "view.fit": "Ctrl+Alt+F"}}),
                             encoding="utf-8")
        original = panel.router.registry, panel.router.entries
        try:
            panel.router.registry = load_registry(None, rebinding)
            panel.router.entries = panel.router.registry["shortcuts"]
            check("A rebinding shows the user's key on the next hover",
                  panel.toolbar_labels.text_for(button(panel.sketch_bar, "Line")) == "Line  (Alt+Shift+L)"
                  and panel.toolbar_labels.text_for(button(panel.model_bar, "Fit")) == "Fit  (Ctrl+Alt+F)")
        finally:
            panel.router.registry, panel.router.entries = original
        # Toolbar: no Undo/Redo arrows; menu, shortcut and search keep them.
        bars = (panel.model_bar, panel.sketch_bar, panel.assembly_bar)
        bar_labels = {action.text() for bar in bars for action in bar.actions()}
        check("Toolbars no longer carry Undo/Redo buttons", not {"Undo", "Redo"} & bar_labels)
        check("Undo/Redo remain in the Document menu", {"Undo", "Redo"} <= {a.text() for a in panel.document_menu.actions()})
        check("Only one primary Extrude tool on the Part Studio bar",
              [a.text() for a in panel.model_bar.actions()].count("Extrude") == 1 and "Remove" not in bar_labels)

        # Search covers toolbar, More menus, sketch tools and shortcut-only actions.
        dialog, field, rows = search("")
        labels = [row[0] for row in rows]
        check("Search lists every tool once", len(labels) == len(set(labels)) and labels.count("Extrude") == 1)
        for name in ("Fillet", "Chamfer", "Spline", "Extrude · Cut", "Undo", "Sketch", "Use"):
            check("Search includes " + name, name in labels)
        report["search_count"] = len(labels)
        dialog.close()
        _, _, rows = search("remove material")
        check("'remove material' finds the Extrude Cut preset first", rows and rows[0][0] == "Extrude · Cut")
        _, _, rows = search("spline")
        check("A sketch tool explains it needs a sketch", rows and rows[0][3] == "Start or edit a sketch first")
        _, _, rows = search("undo")
        check("Undo is searchable with its shortcut", rows and rows[0][0] == "Undo" and rows[0][1] == "Ctrl+Z")
        panel.tool_search_dialog.close()

        # Reopen after the closed dialog was natively deleted, repeatedly, with
        # each cycle searching, activating a result or closing.
        for cycle in range(4):
            QtCore.QCoreApplication.sendPostedEvents(None, QtCore.QEvent.DeferredDelete)
            wait(20)
            dialog, field, rows = search("measure" if cycle % 2 else "fit")
            check("Search reopens after deletion (cycle %d)" % cycle, dialog.isVisible() and rows)
            check("Opening again while visible reuses the dialog (cycle %d)" % cycle,
                  panel.show_tool_search() is dialog)
            if cycle % 2:
                dialog.close()
            else:
                QtTest.QTest.keyClick(field, QtCore.Qt.Key_Return)
                wait(80)
                check("Activating a result closes search (cycle %d)" % cycle, not isValid(dialog) or not dialog.isVisible())
        QtCore.QCoreApplication.sendPostedEvents(None, QtCore.QEvent.DeferredDelete)
        wait(20)
        check("Closed search dialog reference is released", panel.tool_search_dialog is None)

        # Search launches the same tool and mode as the toolbar.
        call("sketch_rectangle", id="Base", width=20, height=10)
        check("A part with only a sketch reads 'Sketches only · mm'", panel.status.text() == "Sketches only · mm" and footer_agrees())
        call("pad", id="Pad", profile="Base", length=6)
        check("A valid solid reads its solid count and volume", panel.status.text().startswith("1 solid(s)")
              and footer_agrees())
        top = "Face" + str(next(i + 1 for i, f in enumerate(doc().Pad.Shape.Faces)
                                if abs(f.CenterOfMass.z - 6) < 1e-7 and f.normalAt(0, 0).z > 0.9))
        call("create_sketch", id="Hole", support={"feature": "Pad", "subelement": top})
        call("add_rectangle", sketch="Hole", width=4, height=4, x=8, y=3)
        panel.select_feature("Hole")
        check("The Hole sketch opens for editing", bool(panel.edit_sketch()))
        call("add_line", sketch="Hole", x1=1, y1=1, x2=2, y2=2, construction=True)
        report["samples"]["editing_status"] = {"status": panel.status.text(), "build_status": panel.state["build_status"]}
        check("Editing a sketch reads 'Editing sketch · mm', never 'Rebuild required', and the footer agrees",
              panel.status.text() == "Editing sketch · mm" and footer_agrees())
        check("Cancel closes the edit and the status returns to the solid", bool(panel.finish_sketch(cancel=True))
              and panel.status.text().startswith("1 solid(s)"))
        panel.select_feature("Hole")
        Gui.Selection.clearSelection()
        Gui.Selection.addSelection(doc().Hole)
        before = (intent_signature(doc()), doc().UndoCount)
        dialog, field, rows = search("cut")
        QtTest.QTest.keyClick(field, QtCore.Qt.Key_Return)
        wait(150)
        check("Search 'cut' opens Extrude in Cut mode", panel.task == "pocket"
              and panel.result_operation.currentData() == "remove" and panel.editor_title.text().startswith("Extrude"))
        result = wait_for_exact(panel.extrusion_preview)
        check("Cut defaults inward (removes material)", result.valid and result.measurements["volume_mm3"] < 1200)
        index = panel.result_operation.findData("add")
        panel.result_operation.setCurrentIndex(index)
        result = wait_for_exact(panel.extrusion_preview)
        check("Switching the same tool to Add extrudes outward", panel.task == "pad" and result.valid
              and result.measurements["volume_mm3"] > 1200)
        panel.result_operation.setCurrentIndex(panel.result_operation.findData("remove"))
        panel.end_type.setCurrentIndex(0)
        QtTest.QTest.keyClicks(panel.depth.lineEdit(), "")
        result = wait_for_exact(panel.extrusion_preview)
        check("Preview leaves the live model unchanged", (intent_signature(doc()), doc().UndoCount) == before)
        QtTest.QTest.mouseClick(panel.confirm, QtCore.Qt.LeftButton)
        wait(200)
        cuts = [o for o in doc().Objects if o.TypeId == "PartDesign::Pocket"]
        check("Cut mode in a native Body creates a native Pocket in one Undo step",
              len(cuts) == 1 and doc().UndoCount == before[1] + 1)
        call("undo")
        check("One Undo removes it", not [o for o in doc().Objects if o.TypeId == "PartDesign::Pocket"])

        # Sketch region fill on a solid face: translucent tint, occluded from below.
        panel.isometric()
        Gui.activeDocument().activeView().fitAll()
        doc().Hole.ViewObject.Visibility = True
        wait(600)
        sketch_center = doc().Hole.getGlobalPlacement().multVec(App.Vector(10, 5, 0))
        bare = doc().Pad.Shape.Faces[int(top[4:]) - 1].CenterOfMass + App.Vector(-7, -3, 0)
        tinted, plain = pixel(sketch_center), pixel(bare)
        report["samples"]["region_on_face"] = tinted
        report["samples"]["bare_face"] = plain
        main.grab().save(str(output / "fill-from-above.png"))
        viewport().grab().save(str(output / "fill-from-above-viewport.png"))
        check("Region on a solid face is tinted, not the bare face color",
              max(abs(a - b) for a, b in zip(tinted, plain)) > 8 and tinted[2] >= tinted[0])
        check("The fill is translucent: the face still shows through (not opaque fill color)",
              tinted != tuple(round(c * 255) for c in panel.sketch_regions.COLOR))
        view = Gui.activeDocument().activeView()
        view.viewBottom()
        view.fitAll()
        wait(600)
        below = pixel(sketch_center - App.Vector(0, 0, 6))
        below_bare = pixel(bare - App.Vector(0, 0, 6))
        report["samples"]["from_below"] = below
        report["samples"]["from_below_bare"] = below_bare
        viewport().grab().save(str(output / "fill-from-below-viewport.png"))
        check("Seen from below, the solid occludes the fill (same as the bare bottom face)",
              max(abs(a - b) for a, b in zip(below, below_bare)) <= 4)
        Gui.Selection.clearSelection()

        # Placed/rotated Body: Studio Add/Cut preview is exact and valid, the
        # deliberate Reverse override is honored, and Confirm matches preview.
        call("new")
        rotation = App.Rotation(App.Vector(1, 1, 0), 50)
        doc().Body.Placement = App.Placement(App.Vector(30, 10, 5), rotation)
        doc().recompute()
        call("inspect")
        call("sketch_rectangle", id="RBase", width=20, height=10)
        call("pad", id="RPad", profile="RBase", length=6, operation="new")
        tip = doc().getObject(doc().RPad.KurtShapeOutputTips[0])
        normal = rotation.multVec(App.Vector(0, 0, 1))
        index, face = next((i, f) for i, f in enumerate(tip.Shape.Faces)
                           if (f.normalAt(*f.Surface.parameter(f.CenterOfMass)) - normal).Length < 1e-6)
        call("create_sketch", id="RTop", support={"feature": tip.Name, "subelement": "Face%d" % (index + 1)})
        center = doc().RTop.Placement.inverse().multVec(face.CenterOfMass)
        call("add_rectangle", sketch="RTop", width=2, height=2, x=center.x - 1, y=center.y - 1)
        base_volume = tip.Shape.Volume
        rotated = {}
        for mode, expected in (("add", 4), ("remove", -4)):
            Gui.Selection.clearSelection()
            Gui.Selection.addSelection(doc().RTop)
            before = (intent_signature(doc()), doc().UndoCount)
            panel.extrude(cut=mode == "remove")
            panel.result_operation.setCurrentIndex(panel.result_operation.findData(mode))
            panel.end_type.setCurrentIndex(0)  # Cut defaults to Through all; compare a 1 mm blind cut
            QtTest.QTest.keyClick(panel.depth.lineEdit(), QtCore.Qt.Key_A, QtCore.Qt.ControlModifier)
            QtTest.QTest.keyClicks(panel.depth.lineEdit(), "1 mm")
            result = wait_for_exact(panel.extrusion_preview)
            rotated[mode] = result.measurements["volume_mm3"] if result.valid else result.error
            check("Rotated Body Studio %s preview is exact and valid" % mode,
                  result.valid and abs(result.measurements["volume_mm3"] - base_volume - expected) < 1e-6)
            check("Rotated Body Studio %s Confirm is enabled" % mode, panel.confirm.isEnabled())
            panel.reverse.click()
            flipped = wait_for_exact(panel.extrusion_preview)
            check("Rotated Body %s Reverse override changes the preview" % mode,
                  not flipped.valid or abs(flipped.measurements["volume_mm3"] - result.measurements["volume_mm3"]) > 1)
            panel.reverse.click()
            result = wait_for_exact(panel.extrusion_preview)
            check("Preview leaves the rotated model unchanged (%s)" % mode,
                  (intent_signature(doc()), doc().UndoCount) == before)
            names = {o.Name for o in doc().Objects}
            QtTest.QTest.mouseClick(panel.confirm, QtCore.Qt.LeftButton)
            wait(300)
            created = [o for o in doc().Objects if o.Name not in names and "KurtShapeOutputTips" in o.PropertiesList]
            committed = doc().getObject(created[0].KurtShapeOutputTips[0]).Shape.Volume if created else None
            rotated[mode + "_committed"] = committed
            check("Rotated Body %s Confirm matches its preview in one Undo step" % mode,
                  committed is not None and abs(committed - result.measurements["volume_mm3"]) < 1e-6
                  and doc().UndoCount == before[1] + 1)
            call("undo")
            check("Undo restores the rotated model (%s)" % mode, intent_signature(doc()) == before[0])
        report["samples"]["rotated_studio"] = rotated
        report.update(passed=True, engine={"FreeCAD": App.Version(), "OCCT": Part.OCC_VERSION})
    except Exception:
        report["error"] = traceback.format_exc()
    finally:
        (output / "gui-result.json").write_text(json.dumps(report, indent=2, default=str), encoding="utf-8")
        panel.shutdown()
        for name in list(App.listDocuments()):
            gui_doc = Gui.getDocument(name)
            if gui_doc and gui_doc.getInEdit():
                gui_doc.resetEdit()
            App.getDocument(name).abortTransaction()
            App.closeDocument(name)
        QtCore.QTimer.singleShot(0, QtGui.QApplication.instance().quit)


QtCore.QTimer.singleShot(1500, validate)
